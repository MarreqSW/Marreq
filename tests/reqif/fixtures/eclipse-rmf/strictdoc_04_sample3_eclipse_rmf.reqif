# TC 1800 'HIS Exchange Process OEM -> SUP (initial)'

# Specification
- ReqIF.Name: Spec1

## R1: Obj-01
- A1: no change
- A2: no change
- E1: one

## R2: Obj-03
- A1: O3.A1 initial
- A2: O3.A2 initial
- E1: one

## R3: Obj-06
- A1: no change
- A2: no change
- E1: one

## R4: Obj-07
- A1: no change
- A2: no change
- E1: one

## R5: Obj-08
- A1: no change
- A2: no change
- E1: one

## R6: Obj-09
- A1: no change
- A2: no change
- E1: one

# Specification
- ReqIF.Name: Spec2
