# MAG8000-LTE-FeatureSpecReqBL4

# Specification: feature specification baseline 4

## adr-10312: feature specification baseline 4 (Heading)

### adr-10313: Introduction (Heading)

#### adr-10314: The current solution (Heading)

#### adr-10306: Migration to LTE IoT (Heading)

## adr-10307: Features (Heading)

### adr-10438: Electronic (Heading)

#### adr-10370: SPI Flash of 32Mbyte will be present on 4G module. (Feature)

#### adr-10373: SMA connector to GSM antenna will be used. (Feature)

#### adr-10372 (Feature)
A so called "data structure" specific to the device will be stored on the uC flash memory. The size of this structure will be 4 KB. This structure will be updated during Manufacturing.

#### adr-10439: Wireless Specification (Heading)

##### adr-10367 (Feature)
The module will embed SARA R422S module which support release 14
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
### adr-10440: SIM Card (Heading)

#### adr-10366 (Feature)
The module will have an interface with SIM

#### adr-10369 (Feature)
The module Sara R422S is provided with an embedded esim solution. (release of SARA R422S with esim option planned for late 2021). Esim is not used for release 1.

#### adr-10368: SIM and esim solution will be supported in the module. (Feature)
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
#### adr-10387: The module will support 1.8V and 3.0V (Feature)
TheÂ module will support 1.8V and 3.0V

#### adr-10389: hot swap should'nt destroy the module, after unplug and plug the module, the mod... (Feature)
hot swap shouldn't destroy the module, after unplug and plug the module, the module should work again.

### adr-10441: Mechanic (Heading)

#### adr-10388: The 4G module will be mounted inside all possible configurations of MAG8000 Tran... (Feature)
The 4G module will beÂ mounted inside all possible configurations of MAG8000 Transmitter enclosure : Remote version, compact version, 230V,24V and battery version.
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
### adr-10434: Environment (Heading)

#### adr-10384: The module will work under following conditions -20Â°C up to 60Â°C. (Feature)
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
### adr-10435: Interface (Heading)

#### adr-10383 (Feature)
The MAG8000 modbus registers defined in document A5E5009542A will be accessible by the module.
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
### adr-10436: Functionalities (Heading)

#### adr-10437: E-mail (Heading)

##### adr-10386 (Feature)
SMTP/SMTPs communication protocol to send data will be supported by the cloud based solution.
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
##### adr-10385 (Feature)
E-mail sent will be compliant to following format : Subject: "Prefix: [IDENTIFIER]"
where [IDENTIFIER] is one of the below, controlled by a parameter.
- Meter Serial Number (6:00248) [STRING][12]
- ApplicationID (8:00656) [STRING][16]
- ApplicationLocation (8:00664) [STRING][16]
Meter Serial number, Application ID and Application Location are read from the host device. The default value of Prefix is "MAG8000".
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
#### adr-10423: FTP (Heading)

##### adr-10381 (Feature)
FTP/FTPs (implicit and explicit will be supported) communication protocol to send data will be supported by the cloud based solution
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
##### adr-10380: The measurmeent data will be sent in "CSV file format" (Feature)
The measurement data will be sent in "CSV file format"
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
#### adr-10431: MQTT-SN/MQTT (Heading)

#### adr-10430: format of process values : (Heading)

##### adr-10382 (Feature)
Process values will be sent out in binaries format (see MQTT commands description A5E48591235A).
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
##### adr-10352: Serial flash memory will be used to buffer process values. (Feature)
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
#### adr-10433: CSV file format stored in SD card and to be used by mag8000 Web APP for serve.IQ connectivity. (Heading)

##### adr-10351 (Feature)
The measurement data collected from the host device will be saved in csv format. The filename of the csv file will be composed of Prefix_[identifier]_[timestamp].csv
Prefix: ordinary text strings, configurable by a parameter;
Timestamp: YYYYMMDD_HHmm;
Identifier: read from the modbus register of the host device - "MeterSerialNo" (248)
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
##### adr-10354 (Feature)
The measurement data read from the host device (TRN) will be compiled in the csv file.
The format of the measurement data stored in the csv file will be :
[timestamp];[FL];[FL unit];[TOT1];[TOT2];[TOT3];[TOT unit];[V1];[V2];[BT];[AL]
timestamp = YYYY-MM-DD HH:MM
FL value = Flow rate value
FL unit = unit of Flow rate
TOT1 = Totalizer 1 value
TOT2 = Totalizer 2 value
TOT3 = Totalizer 3 value
TOT unit = Totalizer unit
V1 = the converted process value from voltage input 1
V2 = the converted process value from voltage input 2
BT = remaining battery capacity (integer value from 0 to 100, i.e. BT%), Transmitter battery capacity wil be used (3030).
AL = alarms in decimal value (host device alarm)
For example, the measurement data stored in the csv file shall as below
2018-01-01 05:02;0.000;m3/h;1.199;0.732;1.199;m3;0.0;0.0;96;5176
2018-01-01 05:03;0.000;m3/h;1.199;0.732;1.199;m3;0.0;0.0;96;5176
2018-01-01 05:04;0.000;m3/h;1.199;0.732;1.199;m3;0.0;0.0;96;5176
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
#### adr-10432: Remote qualification certificate (to be discussed with web APP team) (Heading)

##### adr-10353 (Feature)
Mag8000 web APP will trigger GET_PARAMETER command in order to get all needed parameter.
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
##### adr-10348: Certificate will be generated by web APP and will be available in PDF format. (Feature)
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
##### adr-10347: certification process will be triggered by customer through Web APP. (Feature)
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
#### adr-10427: Voltage input readings (nice to have), to be discussed during MF concept. (Heading)

##### adr-10350: Maximum error of this voltage input will be 3% accross temperature range. (Feature)

##### adr-10349 (Feature)
The activation of the two Voltage input can be activated through "AnalogInputsAcquisitionControl"

##### adr-10346 (Feature)
The product will support two voltage input :Supply voltage range provided by the product: 5 VDC +/- 50 mV
Supply current range: max. 5 mA
Input range: 0 ... 5 VDC
Typical ON time (sample time) during measurement: 100ms
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
##### adr-10345 (Feature)
The product will have four settable conversion factors, "slopeAnalogInput1" , "slopeAnalogInput2"; "OffsetAnalogInput1"; "OffsetAnalogInput2".

##### adr-10364: 12 bits resolution will be implemented, for voltage input measurement. (Feature)

##### adr-10361: the calculated value (taking into account slopeAnalogInput and OffsetAnalogInput) should be saved in measurement data. (Feature)

##### adr-10360 (Feature)
Calculated value (with the customer factor) , rounded three digit after decimal will be displayed.

##### adr-10363: In case the AnalogInputsAcquisitionControl is disabled following parameters should exhibit 0 value in SD card and in sent measurements : AnalogValue1 and AnalogValue2. (Feature)

#### adr-10426: First transmission protocol (Heading)

##### adr-10362 (Feature)
A screening procedure over the MNO (mobile network operator profile) will be present on the 4G module for connectivity purposes (different regions codes). This functionnality will be handle by the com module library. In order to harvest power the radio access technology priority should be following 4G NB IoT 4G Cat M1 2G.

#### adr-10429: Data collection and transmission (Heading)

##### adr-10357: The module will have a configurable data collection and is continuous ( 60 to 86400) "DataCollectionInterval" (Feature)
The module will have a configurable data collection and is continuous ( 60 to 86400). "DataCollectionInterval". Default value is 600.
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
##### adr-10356 (Feature)
The module will have a configurable data transmission and is continuous (60 to 2678400 seconds)."TransmissionInterval". Default value should be 10800 seconds.
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
##### adr-10359 (Feature)
In case configurable parameter "AutoAdaptiveControl" is enable, the transmission interval will go automatically to 30 min if parameter "PowerSupply" (power supply) is set up to 1. In case this parameter is set to 0 this features will not work. In case the data transmission interval is below 30 min the autoadaptive features will not be enabled.
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
##### adr-10358 (Feature)
In case the data transmission interval is below 15 min the autoadaptive features will not be enabled.
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
##### adr-10355 (Feature)
The module will have a configurable paging interval and is continuous (60 to 2678400 seconds) "PagingInterval", this interval will be valid only if it less than data transmission interval. A parameter "pagingcontrol" will enable/disable the paging interval functionnality. Default value should be 3600 seconds.
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
##### adr-10334 (Feature)
The paging interval feature shall not work if the auto-adaptive transmission feature is activated.

##### adr-10333 (Feature)
IntervalSynchronisationTime parameter will be used to set up synchronisation time. Unix UTC time stamp will be used. Default value will be 0xFFFFFFFF.

#### adr-10428: 4G module simplified EDD file description (Heading)

##### adr-10330 (Feature)
EDD file will describe the 4G module specific parameter accessible as described in the parameter list A5EA5E5009542A

##### adr-10329: EDD file will stored inside the Uc internal flash memory (Feature)
EDD file will be integrated into application firmware

##### adr-10332: EDD file will be flashed during MF process (Feature)

##### adr-10331: EDD file will contain a version number "EDDFileVersion" Parameter (5000). (Feature)
EDD version will be integrated into the "firmwareversion"

##### adr-10326: EDD file mapping will be done through parameter name. (Feature)

#### adr-10425: Historical data (Heading)

##### adr-10325: The module will support a micro SD card. (Feature)
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
##### adr-10328 (Feature)
Data will be stored based on data collection interval "DataCollectionInterval", earliest data shall overwritte the oldest data in case of full memory.

##### adr-10327: the module should be able to run without SDcard. storage of CSV file will be drop... (Feature)
the module should be able to run without SDcard storage of CSV file will be dropped in that case.
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
##### adr-10342 (Feature)
User Manual will indicate that SD card shouldn't be removed without using function button.
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
#### adr-10424: Error handling (Heading)

##### adr-10344: retry mechanism: done internally by Thingstream SDK. (Feature)

##### adr-10343 (Feature)
The module will log all failed data transmission by date in SD card if its plugged in.

##### adr-10339 (Feature)
If SD card is not present the logging data will be saved in external SPI Flash Memory.

##### adr-10338: The signal network errors will be trigered through "NetworkSignalStrengthAlarmThreshold" (Feature)
If The signal strenght network is below"NetworkSignalStrengthAlarmThreshold", then AL01 "Network signal strength below limit" would be sent.

#### adr-10449: Alarm handling (Heading)

##### adr-10341 (Feature)
The module will send the alarms to MQTT Broker in case errors are detected with the time stamp. Refer to chapter "Real time alarm message format." of document MQTT Interface .

##### adr-10340: flag will be sent with all timestamps where the alarm occured. (Feature)

##### adr-10336 (Feature)
The module will include in the last column of measurement line of CSV file parameter "faultstatus". Please note it's host device only.

##### adr-10335 (Feature)
The module will send a real time alarm through MQTT communication channel in case parameter "faultstatus" is different from previous reading.

##### adr-10337 (Feature)
A "ModuleAlarmMask" will be supported for the customer to select what alarms of the module shall trigger the real-time alarm, i.e. the real-time alarm is activated if the corresponding bit of the alarm mask is set to 1. The alarm mask functions shall not disable the real-time alarms of the host device.

#### adr-10446: Product configuration (Heading)

##### adr-10407 (Feature)
Parameters as define in 4Gmodule parameters list (A5E38431885A) will be configurable through MQTT configuration channel.

#### adr-10445: Supplementary Functionalities (Heading)

##### adr-10406 (Feature)
Clock synchronization of the module will be done through synchronisation in UNIX-UTC timing provided by thingstream server. . This clock will be synchronized regularly.

##### adr-10409 (Feature)
the firmware of the module will be over the air updatable (postpone to release 2).

##### adr-10408 (Feature)
Battery capacity in the process values wil be read out from following TRN modbus register "BatteryCapacity" (3030)

##### adr-10403 (Feature)
a leakage detection test will be launched on demand. Three parameters will be used to start this test. Start parameter and period parameter. There is a parameter "LeakageWindowssControl" to enable this functionnality , if period parameter is set to a valid period it will be repeated each 24h hours.
at 15 sec interval if the actual excitation freq (reg 238) = 1/15Hz, 1/5Hz, 1.5625Hz, 3.125Hz, 6.25Hz, orÂ
at 30 sec interval if the actual excitation freq (reg 238) = 1/30Hz, orÂ
at 60 sec interval if the actual excitation freq (reg 238) = 1/60Hz.
Mapping values of ExcitationFreqNo (238) areÂ :
0= 1/15Hz
1= 1/5Hz
2= 1.5625Hz
3= 3.125Hz
4= 6.25Hz
5= 1/30Hz
6= 1/60Hz

##### adr-10402 (Feature)
Firmware over the air (FOTA) of the uC and the cellular modem are not foreseen in this release.

#### adr-10448: Product Security (Heading)

##### adr-10405: SD card data are unencrypted. (Feature)

#### adr-10447: Usability/commissioning (needs to be discussed) (Heading)

##### adr-10404 (Feature)
Commissioning is defined as the action of plugging the 4g module on the host device for the first time. Communication module shall communicate by default.

##### adr-10399 (Feature)
During each power up a LED placed on the module and visible when the enclosure is not on the transmitter will give following status : module on/off (green); module connected to thingstream (blue LED); both LED on for 5 min.

##### adr-10397 (Feature)
The module will be hot swappable without damaging the Transmitter. Perennity of data on the module is not guaranteed in case the FunctionButton is not used properly.

#### adr-10443: Accessories and spare parts (Heading)

##### adr-10415: The communication module will be available as spare part (Feature)

##### adr-10417: Antenna will be available as spare part (Feature)

##### adr-10412: The voltage input cable will be available as spare part (Feature)

### adr-10442: Sitrans IQ App (Heading)

### adr-10444: Use case : (Heading)
